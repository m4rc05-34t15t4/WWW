FME workspace MI_ligacao_FME-2020.0_V1.0.0.fmw

Parameters:
- SourceDataset_POSTGIS = Controle_PE   # Database
- FEATURE_TYPES = public.edicao

Readers:
- POSTGIS_1: POSTGIS from $(SourceDataset_POSTGIS) in EPSG:4674

Note: : Controle_PE [POSTGIS] EDICAO
edicao (reader POSTGIS_1)
    attributes: id int8,PrimaryKey, mi varchar(80), bloco varchar(80), status varchar(80), editor varchar(80), inicioedicao varchar(80), terminoedicao varchar(80), revisor1 varchar(80), inicio1rev varchar(80), termino1rev varchar(80), servidor varchar(80), niveis varchar(200), densidade varchar(200), revisor2 varchar(80), inicio2rev varchar(80), termino2rev varchar(80), nome_carta varchar(80), inom text, iniciocorrecao1 varchar(80), terminocorrecao1 varchar(80), iniciocorrecao2 varchar(80), terminocorrecao2 varchar(80), impressa bool, ligacao bool, totalobj varchar(200), total_p numeric(20,0), total_l numeric(20,0), total_a numeric(20,0), txt_p numeric(20,0), txt_l varchar(200),
      o varchar(80), s varchar(80), se varchar(80), so varchar(80), l varchar(80), n varchar(80), no varchar(80), ne varchar(80), linha int2, coluna int2, regiao text
    -> AttributeCreator
AttributeCreator
    ATTR_TABLE = SET_TO _escala = FME_CONDITIONAL:DEFAULT_VALUE'_FME_NO_OP_'BOOL_OP;OR;COMPOSITE_TEST;1;TEST @StringLength(@Value(mi)) >= 9'25K'BOOL_OP;OR;COMPOSITE_TEST;1;TEST @StringLength(@Value(mi)) >= 7'50K'BOOL_OP;OR;COMPOSITE_TEST;1;TEST @StringLength(@Value(mi)) >= 4'100K'FME_NUM_CONDITIONS4___
    -> SpatialRelator [Requestor]
    -> _All_
    -> SpatialRelator [Supplier]
SpatialRelator
    AGGREGATE_HANDLING = Yes
    CALC_CARD = No
    CURVE_BOUNDARY_RULE_PARAM = Default Rule
    LIST_ATTRS_TO_INCLUDE = _escala mi
    LIST_NAME = _relationships
    PREDICATES = INTERSECTS
    SUCCESS_ATTR = _related_candidates
    -> SpatialRelator_Output
SpatialRelator_Output: Inspector
CenterPointReplacer [off]
    POINTTYPE = CENTER
    POINT -> _All_
_All_: Inspector
